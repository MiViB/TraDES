--  $Id: trajgraph.asn,v 1.8 2004/07/06 20:20:46 hfeldman Exp $
--  
--  NOTE:  This specification is in a variant of ASN.1 1990 that may not
--         be compatible with newer ASN.1 tools.  This specification also
--         depends on public domain specifications available from the 
--         U.S. National Center for Biotechnology Information (NCBI)
--         ftp://ncbi.nlm.nih.gov/toolbox/ncbi_tools/
--         http://www.ncbi.nlm.nih.gov/Toolbox/
-- 
--**********************************************************************
--
--  Definitions for Trajectory Graph files
--
--  By Howard Feldman 
--  Samuel Lunenfeld Research Institute
--  600 University Avenue, Toronto, Ontario
--
--  January 1999
--
--**********************************************************************

TrajGraph DEFINITIONS ::=

BEGIN

EXPORTS TGraph, TGraph-header;

IMPORTS Seq-entry FROM NCBI-Seqset
	Biostruc FROM MMDB;

TGraph ::= SEQUENCE {
	tgheader		TGraph-header,
	datacdx			TGraph-trajdata,
	datadbf			TGraph-trajdata,
	datafpt			TGraph-trajdata }

TGraph-header ::= SEQUENCE {
	bsstub			Biostruc OPTIONAL,
	seq			TGraph-Seq,
	bseq			SET OF Seq-entry OPTIONAL,
	seqlen			TGraph-SeqLen,
	bberrtol		REAL,
	bbacc			REAL,
	numrot			INTEGER,
	incsize			REAL,
	startbb			REAL,
	atmbncbb		REAL,
	atmbncsc		REAL,
	bumph			INTEGER,
	distconstr		SEQUENCE OF TGConstraint-Data OPTIONAL,
	constrfile		VisibleString,
	trajtype		INTEGER,
	trajdiv			INTEGER,
	timeout			INTEGER,
	walktype		INTEGER,
	tgunits			INTEGER,
	tunnel			REAL OPTIONAL }

TGraph-Seq ::= VisibleString

TGraph-SeqLen ::= INTEGER

TGraph-trajdata ::= OCTET STRING

TGConstraint-Data ::= SEQUENCE {
	res1			TGConstraint-ResidueID,
	res2			TGConstraint-ResidueID,
	atomname1		TGConstraint-AtomName,
	atomname2		TGConstraint-AtomName,
	meandist		TGConstraint-Dist,
	mindelta		TGConstraint-Dist,
	maxdelta		TGConstraint-Dist,
	angle1			TGConstraint-Angle,
	angle2			TGConstraint-Angle,
	dihedral01		TGConstraint-Angle,
	dihedral12		TGConstraint-Angle,
	dihedral23		TGConstraint-Angle,
	prob			REAL }

TGConstraint-ResidueID ::= INTEGER

TGConstraint-AtomName ::= VisibleString

TGConstraint-Dist ::= REAL
TGConstraint-Angle ::= REAL

SSPrediction-OneState ::= SEQUENCE {
	pred			VisibleString,
	cksum			VisibleString }

----------------------------------
-- last:	allow for doubly linked list
-- alnname:     name of structure fragment comes from
-- qseq:        sequence of query in fragment
-- tseq:        sequence of template in fragment
-- qstart:      residue number in query at start of fragment
-- tstart:      residue number in template at start of fragment
-- seglen:      length of fragment
-- isgap:       FALSE if gapless fragment, TRUE otherwise
----------------------------------
HomTraj-Frag ::= SEQUENCE {
	last		HomTraj-Frag OPTIONAL,
        alnname         VisibleString,
        qseq            VisibleString,
        tseq            VisibleString,
        qstart          INTEGER,
        tstart          INTEGER,
        seglen          INTEGER,
        isgap           BOOLEAN DEFAULT FALSE }

----------------------------
-- qseq:        Query sequence
-- qlen:        Length of query sequence
-- cddeval:     E value from CDD, if any
-- alneval:     E value from other source
-- frags_pri:   The fragments derived from the primary alignment
-- frags_sec:   The fragments derived from the secondary alignments, if any
----------------------------
HomTraj-Alignment ::= SEQUENCE {
        qseq            VisibleString,
        qlen            INTEGER,
        cddeval         REAL,
        alneval         REAL,
        frags-pri       SEQUENCE OF HomTraj-Frag,
        frags-sec       SEQUENCE OF HomTraj-Frag OPTIONAL }

END

--  $Log: trajgraph.asn,v $
--  Revision 1.8  2004/07/06 20:20:46  hfeldman
--  Added homtraj object
--
--  Revision 1.7  2002/07/25 16:33:08  feldman
--  Added tunnelling to header
--
--  Revision 1.6  2002/05/27 19:50:10  feldman
--  Fixed typo
--
--  Revision 1.5  2002/05/27 17:19:39  feldman
--  Added SSpred object
--
--  Revision 1.4  2001/01/16 22:01:35  feldman
--  Updated contraints to now have the proper 6 degrees of freedom.
--  Support still needs to be added for Phi-Psi walk
--
--  Revision 1.3  2000/09/15 20:35:38  feldman
--  Added angle and dihedral to distance constraints
--
--  Revision 1.2  2000/08/09 19:12:18  feldman
--  -minor bugfix update and fixed up makefiles removing USEDSSP
--  -added bioseq/seq-entry to trajectory graph header when using
--   unfoldtraj or val2trj
--
--  Revision 1.1.1.1  2000/06/09 18:13:58  feldman
--  TraDES project
--
